FME workspace cps_areas.fmw

Parameters:
- SourceDataset_SHAPEFILE = $(FME_MF_DIR)data\Police_Force_Areas__December_2016__Boundaries.shp   # Source Esri Shapefile(s)
- SourceDataset_CSV2_3 = $(FME_MF_DIR)data\areas.csv   # Source CSV (Comma Separated Value) File(s)
- SourceDataset_CSV2 = $(FME_MF_DIR)data\population.csv   # Source CSV (Comma Separated Value) File(s)
- DestDataset_SHAPEFILE =   # Destination Esri Shapefile Folder

Readers:
- SHAPEFILE_1: SHAPEFILE from $(SourceDataset_SHAPEFILE)
- CSV2_2: CSV2 from $(SourceDataset_CSV2_3)
- CSV2_1: CSV2 from $(SourceDataset_CSV2)

Writers:
- SHAPEFILE_2: SHAPEFILE to $(DestDataset_SHAPEFILE)

Police_Force_Areas__December_2016__Boundaries (reader SHAPEFILE_1)
    attributes: objectid short, pfa16cd char(9), pfa16nm char(19), bng_e long, bng_n long, long double, lat double, st_areasha double, st_lengths double
    -> FeatureMerger [REQUESTOR]
CSV (reader CSV2_2)
    attributes: cps_area string, police_force string
    -> FeatureMerger [SUPPLIER]
FeatureMerger
    ATTR_ACCUM_MODE = Merge Supplier
    ATTR_CONFLICT_RES = Use Requestor
    IGNORE_NULLS = No
    JOIN_KEYS = @Value(pfa16nm) @Value(police_force) AUTO
    MERGE_TYPE = Attributes Only
    PROCESS_DUPS = NO
    REJECT_NULL_MISSING_KEYS = No
    SUPPLIERS_FIRST = No
    MERGED -> Dissolver
Dissolver
    ACCUM_INPUT_ATTRS = Use Attributes From One Feature
    CLEANING_TOLERANCE = Automatic
    CONNECT_Z_MODE = First Wins
    DEAGGREGATE_INPUT = Yes
    AREA -> FeatureMerger_2 [REQUESTOR]
CSV (reader CSV2_1)
    attributes: cps_area string, convictions uint16, population uint32, convictions_per_000 real64
    -> FeatureMerger_2 [SUPPLIER]
FeatureMerger_2
    ATTR_ACCUM_MODE = Merge Supplier
    ATTR_CONFLICT_RES = Use Requestor
    IGNORE_NULLS = No
    JOIN_KEYS = @Value(cps_area) @Value(cps_area) AUTO
    MERGE_TYPE = Attributes Only
    PROCESS_DUPS = NO
    REJECT_NULL_MISSING_KEYS = No
    SUPPLIERS_FIRST = No
    MERGED -> cps_shapes (writer SHAPEFILE_2)
cps_shapes (writer SHAPEFILE_2)
    attributes: objectid short, pfa16cd char(9), pfa16nm char(19), bng_e long, bng_n long, long double, lat double, st_areasha double, st_lengths double, cps_area char(254), conviction long, population double, convicti00 double
